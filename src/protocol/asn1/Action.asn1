ActionModule DEFINITIONS AUTOMATIC TAGS ::= BEGIN
    IMPORTS Number, Version, Hash 
    FROM BasicModule
    Account 
    FROM AccountModule;

Action ::= SEQUENCE {
    version         Version,
    date            UTCTime,
    contract        Hash,
    parent          Hash,
    model           ANY
}

END
