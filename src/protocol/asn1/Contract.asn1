ContractModule DEFINITIONS AUTOMATIC TAGS ::= BEGIN
    IMPORTS Version, Hash, Key 
        FROM BasicModule
        Roll
        FROM SecurityModule
        Account
        FROM AccountModule;


Contract ::= SEQUENCE {
    version         Version,
    id              Hash,
    name            UTF8String,
    owner           Hash,
    permissions     SEQUENCE OF Hash,
    code            OCTET STRING
}



END
