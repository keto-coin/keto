PrivateKeyModule DEFINITIONS AUTOMATIC TAGS ::= BEGIN
    IMPORTS Version, BerEncoding
        FROM BasicModule;

PrivateKey ::= SEQUENCE {
    version         Version,
    -- the encrypted private key value
    key             EncyptedData
}


END
