ChangeSetModule DEFINITIONS AUTOMATIC TAGS ::= BEGIN
    IMPORTS Version, Signature, BinaryData, Hash, Status
        FROM BasicModule;

ChangeData ::= CHOICE {
    asn1Change         ANY,
    binaryChange       BinaryData
}


ChangeSet ::= SEQUENCE {
    version             Version,
    transactionHash     Hash,
    accountHash         Hash,
    status              Status,
    changes    SEQUENCE OF ChangeData
}

SignedChangeSet ::= SEQUENCE {
    changeSet       ChangeSet,
    changeSetHash   Hash,
    signature       Signature
}

END
