BlockChainModule DEFINITIONS AUTOMATIC TAGS ::= BEGIN
    IMPORTS Number, Hash, Version, Signature
        FROM BasicModule
        Account 
        FROM AccountModule
        Action
        FROM ActionModule
        Transaction, SignedTransaction, ChangeSet, SignedChangeSet, TransactionMessage
        FROM TransactionModule;


Block ::= SEQUENCE {
    version             Version,
    date                UTCTime,
    parent              Hash,
    transactions        SEQUENCE OF TransactionMessage,
    merkelRoot          Hash
}

SignedBlock ::= SEQUENCE {
    version         Version,
    date            UTCTime,
    parent          Hash,
    block           Block,
    hash            Hash,
    signature       Signature
}

END
