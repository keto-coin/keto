SecurityModule DEFINITIONS AUTOMATIC TAGS ::= BEGIN
    IMPORTS Version, Hash
        FROM BasicModule;

Roll ::= SEQUENCE {
    version         Version,
    id              Hash,
    name            UTF8String
}


END
