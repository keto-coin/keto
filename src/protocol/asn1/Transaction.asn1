TransactionModule DEFINITIONS AUTOMATIC TAGS ::= BEGIN
    IMPORTS Number, Hash, Version, Key, Signature, Status
        FROM BasicModule
        Account 
        FROM AccountModule
        Action
        FROM ActionModule
        ChangeSet, SignedTransaction
        FROM ChangeSetModule;

Transaction ::= SEQUENCE {
    version         Version,
    date            UTCTime,
    value           Number,
    parent          Hash,
    -- the source account for the transaction
    sourceAccount   Hash,
    -- the target account for the transaction
    targetAccount   Hash,
    actions         SEQUENCE OF Action
}

SignedTransaction ::= SEQUENCE {
    version         Version,
    transaction     Transaction,
    transactionHash Hash,
    signature       Signature
}

TransactionTrace ::= SEQUENCE {
    traceHash       Hash,
    signature       Signature
}


TransactionMessage ::= SEQUENCE {
    version             Version,
    -- transaction header information
    sourceAccount       Hash,
    targetAccount       Hash,
    feeAccount          Hash,
    transactionHash     Hash,
    signature           Signature,
    -- transaction 
    signedTransaction   SignedTransaction,
    transactionTrace    SEQUENCE OF TransactionTrace,
    -- status and changeset
    currentStatus       Status,
    changeSet           SEQUENCE OF SignedChangeSet
}




END
